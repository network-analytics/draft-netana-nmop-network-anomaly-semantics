module ietf-network-anomaly-symptom-cbl {
    yang-version 1.1;
    namespace "urn:ietf:params:xml:ns:yang:ietf-network-anomaly-symptom-cbl";
    prefix smcblsymptom;

    import ietf-relevant-state {
        prefix rsn;
        reference
          "RFC XXX: Relevant State and Relevant State Notification";
    }

  organization "IETF NMOP (Network Management Operations) Working Group";
  contact
    "WG Web:   <http:/tools.ietf.org/wg/netconf/>
     WG List:  <mailto:nmop@ietf.org>

     Authors:  Thomas Graf
               <mailto:thomas.graf@swisscom.com>
               Wanting Du
               <mailto:wanting.du@swisscom.com>
               Alex Huang Feng
               <mailto:alex.huang-feng@insa-lyon.fr>
               Vincenzo Riccobene
               <mailto:vincenzo.riccobene@huawei-partners.com>";
    description
        "This module defines the semantic grouping to be used by a
		 Service Disruption Detection Systems. The defined objects is
		 used to augment the anomaly container. Describing the
		 symptoms action, reason and concern-score.
		 
         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).

         This version of this YANG module is part of RFC XXXX; see the RFC
         itself for full legal notices.";

    revision 2025-03-06 {
        description
          "Initial version";
        reference
          "RFC XXX: Semantic Metadata Annotation for Network Anomaly Detection";
    }
    typedef score {
        type uint8 {
            range "0 .. 100";
        }
        description "Number indicating a score between 0 and 100";
    }
    
    grouping cbl-symptom {
        description "Semantic definining a symptom detected for a connectivity service";
        leaf action {
            type string;
            description "action";
        }
        leaf reason {
            type string;
            description
                "reason";
        }
        leaf cause {
            type string;
            description
                "cause";
        }
        choice plane {
            description
                "Network Plane affected by the symptom";
            case forwarding {
                leaf forwarding {
                    type empty;
					description
						"forwarding plane";
                }
            }
            case control {
                leaf control {
                    type empty;
					description
						"control plane";
                }
            }
            case management {
                leaf management {
                    type empty;
					description
						"management plane";
                }
            }
        }
    }

    augment /rsn:relevant-state/rsn:anomalies/rsn:symptom {
        description 
            "Provide extension for the symptom description, 
			specifically for connectivity services to the 
			relevant state container";
        uses cbl-symptom;
    }

    augment /rsn:relevant-state-notification/rsn:anomalies/rsn:symptom {
        description 
            "Provide extension for the symptom description, 
			specifically for connectivity services to the 
			relevant state notification";
        uses cbl-symptom;
    }
}
