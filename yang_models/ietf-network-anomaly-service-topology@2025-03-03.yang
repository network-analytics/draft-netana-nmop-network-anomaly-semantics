module ietf-network-anomaly-service-topology {
    yang-version 1.1;
    namespace "urn:ietf:params:xml:ns:yang:ietf-network-anomaly-service-topology";
    prefix smtopology;

    import ietf-inet-types {
        prefix inet;
        reference
			"RFC 6991: Common YANG Data Types";
    }
    import ietf-relevant-state {
        prefix rsn;
        reference
          "RFC XXX: Relevant State and Relevant State Notification";
    }
	
  organization "IETF NMOP (Network Management Operations) Working Group";
  contact
    "WG Web:   <http:/tools.ietf.org/wg/netconf/>
     WG List:  <mailto:nmop@ietf.org>

     Authors:  Thomas Graf
               <mailto:thomas.graf@swisscom.com>
               Wanting Du
               <mailto:wanting.du@swisscom.com>
               Alex Huang Feng
               <mailto:alex.huang-feng@insa-lyon.fr>
               Vincenzo Riccobene
               <mailto:vincenzo.riccobene@huawei-partners.com>";
    
    description 
        "This module defines the symptom container to be used by a network
         anomaly detection system. The defined objects can be used to
         augment operational network collected observability data and 
         analytical problem data equally. Describing the relevant-state
		 of observed symptoms.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).

         This version of this YANG module is part of RFC XXXX; see the RFC
         itself for full legal notices.";

    revision 2025-03-03 {
        description
          "Initial version";
        reference
          "RFC XXX: Semantic Metadata Annotation for Network Anomaly Detection";
    }

	grouping vpn-service-grouping {
		description 
			"Connectivity service of type VPN. This grouping is 
			used to augment the relevant-state container";
		container vpn-service-container {
			description 
				"Definition of a container including a list of 
				VPN Service instances";
			list vpn-service {
				key "vpn-id";
				description "List of VPN services of interest";
				leaf uri {
					type inet:uri;
					description
						"URI to viusalize the VPN service inventory.";
				}				
				leaf vpn-id {
					type string;
					mandatory true;
					description
						"Unique ID of the VPN connectivity service";
				}
				leaf vpn-name {
					type string;
					description
						"Name of the VPN connectivity service";
				}
				leaf-list site-ids {
					type string;
					description
						"List of unique site ID's of the VPN connectivity service";
				}
				leaf change-start-time {
					type yang:date-and-time;
					description
						"Start date and time of the VPN service maintenance window";
				}
				leaf change-end-time {
					type yang:date-and-time;
					description
						"End date and time of the VPN service maintenance window";
				}				
				leaf change-id {
					type yang:uuid;
					description
						"Unique identifier of VPN service maintenance window";
				}
			}
		}
	}

	grouping vpn-node-termination-grouping {
		description 
			"Node Termination for the VPN Service instance. 
			This grouping is used to augment the relevant-state container";
		container vpn-node-termination-container {
			description 
				"Definition of a container including a list of VPN Node Terminations";
			list vpn-node-termination {
				key "hostname route-distinguisher";
				description "List of Node Terminations of interest";
				leaf hostname {
					type inet:host;
					mandatory true;
					description
						"The hostname of the network node according to
						[RFC1213]. This value is usually configured on
						the node by the administrator to uniquely
						identify the node in the network.";
				}
				leaf route-distinguisher {
					type string;
					mandatory true;
					description
						"The BGP route-distinguisher obtained through
						IPFIX IE90 mplsVpnRouteDistinguisher or BMP
						route-monitoring or peer_up message type.";
				}		
				leaf-list peer-ip {
					type inet:ip-address;
					description
							"The BGP peering IP address learned through
							BMP route-monitoring, peer_up or peer_down
							message type.";
				}
				leaf-list next-hop {
					type inet:ip-address;
					description
						"The BGP next-hop IP address learned through
						BMP route-monitoring message type.";
				}
				leaf-list interface-id {
					type int32;
					description
						"The interface identifier obtained through
						IPFIX IE10 ingressInterface, IE14 
						egressInterface or
						ietf-interfaces:interfaces/interface/if-index.";
				}
			}
		}
	}

	augment /rsn:relevant-state/rsn:anomalies/rsn:service {
		description 
			"Provide extension for the service description, 
			specifically for connectivity services to the 
			relevant state container";
		uses vpn-service-grouping;
    }

	augment /rsn:relevant-state-notification/rsn:anomalies/rsn:service {
		description 
			"Provide extension for the service description, 
			specifically for connectivity services to the 
			relevant state notification";
		uses vpn-service-grouping;
    }

    augment /rsn:relevant-state/rsn:anomalies/rsn:service {
		description 
			"Provide extension for the service description, 
			specifically for connectivity services to the 
			relevant state container";
		uses vpn-node-termination-grouping;
	}

	augment /rsn:relevant-state-notification/rsn:anomalies/rsn:service {
		description 
			"Provide extension for the service description, 
			specifically for connectivity services to the 
			relevant state notification";
		uses vpn-node-termination-grouping;
	}
}
