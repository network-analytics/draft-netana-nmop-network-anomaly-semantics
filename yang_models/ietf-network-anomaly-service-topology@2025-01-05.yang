module ietf-network-anomaly-service-topology {
    yang-version 1.1;
    namespace "urn:ietf:params:xml:ns:yang:ietf-network-anomaly-service-topology";
    prefix smtopology;

    import ietf-inet-types {
        prefix inet;
        reference
			"RFC 6991: Common YANG Data Types";
    }
    import ietf-relevant-state {
        prefix rsn;
        reference
          "RFC XXX: Relevant State and Relevant State Notification";
    }
	
  organization "IETF NMOP (Network Management Operations) Working Group";
  contact
    "WG Web:   <http:/tools.ietf.org/wg/netconf/>
     WG List:  <mailto:nmop@ietf.org>

     Authors:  Thomas Graf
               <mailto:thomas.graf@swisscom.com>
               Wanting Du
               <mailto:wanting.du@swisscom.com>
               Alex Huang Feng
               <mailto:alex.huang-feng@insa-lyon.fr>
               Vincenzo Riccobene
               <mailto:vincenzo.riccobene@huawei-partners.com>
               Antonio Roberto
               <mailto:antonio.roberto@huawei.com>";
    description
        "This module defines the symptom conatiner to be used by a network
         anomaly detection system. The defined objects can be used to
         augment operational network collected observability data and 
         analytical problem data equally. Describing the relevant-state
		 of observed symptoms.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).

         This version of this YANG module is part of RFC XXXX; see the RFC
         itself for full legal notices.";

    revision 2025-01-05 {
        description
          "Initial version";
        reference
          "RFC XXX: Semantic Metadata Annotation for Network Anomaly Detection";
    }

	grouping vpn-service-grouping {
	    description "VPN connectivity service group.";
		container vpn-service-container {
			description "VPN connectivity service container.";
			list vpn-service {
				description "Identifier leafs.";
				key "vpn-id";
				leaf vpn-id {
					type string;
					description
						"Unique ID of the VPN connectivity service";
				}
				leaf vpn-name {
					type string;
					description
						"Name of the VPN connectivity service";
				}
				leaf-list site-ids {
					type string;
					description
						"List of unique site ID's of the VPN connectivity service";
				}
			}
		}
	}

	grouping vpn-node-termination-grouping {
	    description "VPN node termination group.";
		container vpn-node-termination-container {
			description "VPN node termination container.";
			list vpn-node-termination {
				description "Identifier leafs.";
				key "hostname route-distinguisher";
					leaf hostname {
						type inet:host;
						description
							"The hostname of the network node according to
							[RFC1213]. This value is usually configured on
							the node by the administrator to uniquely
							identify the node in the network.";
					}
					leaf route-distinguisher {
						type string;
						description
							"The BGP route-distinguisher obtained through
							IPFIX IE90 mplsVpnRouteDistinguisher or BMP
							route-monitoring or peer_up message type.";
					}		
					leaf-list peer-ip {
						type inet:ip-address;
						description
							"The BGP peering IP address learned through
							BMP route-monitoring, peer_up or peer_down
							message type.";
					}
					leaf-list next-hop {
						type inet:ip-address;
						description
							"The BGP next-hop IP address learned through
							BMP route-monitoring message type.";
					}
					leaf-list interface-id {
						type int32;
						description
							"The interface identifier obtained through
							IPFIX IE10 ingressInterface, IE14 
							egressInterface or
							ietf-interfaces:interfaces/interface/if-index.";
					}
			}
		}
	}

	augment /rsn:relevant-state/rsn:anomalies/rsn:service {
		uses vpn-service-grouping;
    }

	augment /rsn:relevant-state-notification/rsn:anomalies/rsn:service {
		uses vpn-service-grouping;
    }

    augment /rsn:relevant-state/rsn:anomalies/rsn:service {
		uses vpn-node-termination-grouping;
	}

	augment /rsn:relevant-state-notification/rsn:anomalies/rsn:service {
		uses vpn-node-termination-grouping;
	}
}
