module ietf-relevant-state {
    yang-version 1.1;
    namespace "urn:ietf:params:xml:ns:yang:ietf-relevant-state";
    prefix rsn;

    import ietf-yang-types {
      prefix yang;
      reference "RFC 6021: Common YANG Data Types";
    }

    import ietf-inet-types {
      prefix inet;
      reference "RFC 6991: Common YANG Data Types";
    }

    organization
      "IETF NMOP Working Group";
    contact
      "WG Web:   <https://datatracker.ietf.org/wg/nmop/>
      WG List:  <mailto:nmop@ietf.org>

      Authors:  Vincenzo Riccobene
                <mailto:vincenzo.riccobene@huawei-partners.com>
                Thomas Graf
                <mailto:thomas.graf@swisscom.com>
                Wanting Du
                <mailto:wanting.du@swisscom.com>
                Alex Huang Feng
                <mailto:alex.huang-feng@insa-lyon.fr>";
    description
        "This module defines the relevant-state container and
	    notifications to be used by a network anomaly detection
	    system. The defined objects can be used to augment
	    operational network collected observability data and 
        analytical problem data equally. Describing the relevant-state
		of observed symptoms.

        Copyright (c) 2025 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).
        
        This version of this YANG module is part of RFC XXXX; see the RFC
        itself for full legal notices.";

    revision 2025-02-26 {
        description
          "Initial version";
        reference
          "RFC XXX: Semantic Metadata Annotation for Network Anomaly Detection";
    }

    typedef score {
        type uint8 {
            range "0 .. 100";
        }
        description "Number that indicates a score between 0 and 100";
    }
    identity network-anomaly-state {
		  description
		    "Base identity for representing the state of the network anomaly";
    }
    identity detection {
      base network-anomaly-state;
      description
        "A problem reached detection state";
    }
    identity validation {
      base network-anomaly-state;
      description
        "A problem reached validation state";
    }
    identity refinement {
      base network-anomaly-state;
      description
        "A problem reached refinement state";
    }
      identity problem-forecasted {
      base detection;
      description
        "A problem has been forecasted, as it is expected that
        the indicated list of symptoms will impact a service
        in the near future";
    }
    identity problem-potential {
      base detection;
      description
        "A problem has been detected with a confidence
        lower than 100%. In order to confirm that this set of
        symptoms are generating service impact, it requires further
        validation";
    }
    identity problem-confirmed {
      base validation;
      description
        "After validation, the problem has been confirmed";
    }
    identity discarded {
      base validation;
      description
        "After validation, the network anomaly has been
        discarded, as there is no evindence that it is causing an
        problem";
    }
    identity analyzed {
      base refinement;
      description
        "The anomaly detection went through analysis to identify
        potential ways to further improve the detection process in
        for future anomalies";
    }
    identity adjusted {
      base refinement;
      description
        "The network anomaly has been solved and analysed.
        No further action is required.";
    }

    identity pattern {
      description 
        "Pattern identified by the Detector.";
    }
    identity drop {
        description
          "Drop of the value";
    }
    identity spike {
        description
          "Spike of the value";
    }
    identity mean-shift {
        description
            "Shift of the mean of the value";
    }
    identity seasonality-shift {
        description 
          "Shift of the seasonality of the value";
    }
    identity trend {
        description
            "Trend exhibited by the value";
    }
    identity other {
        description
          "Any other type of pattern";
    }

    grouping relevant-state-grouping {
        description "Relevant State is a state that could lead to
            problems or might be clear indications of problem already happening";
        leaf description {
            type string;
            description
                "Textual description of the fault";
        }
        leaf start-time {
            type yang:date-and-time;
            mandatory true;
            description
                "Date and time indicating the beginning of the fault";
        }
        leaf end-time {
            type yang:date-and-time;
            description
                "Date and time indicating the end of the fault";
        }
    }

    grouping annotator-grouping {
        description "Annotator represents the entity that produced the
        annotation (it is either a human or an algorithm)";
        leaf name {
            type string;
            mandatory true;
            description 
                "Name of the annotator (either user or algorithm)
                If it is an algorithm, the name can also include 
                the version.";
        }
        choice annotator-type {
            description "An annotator can be either a human user or a
            programmatic entity, such as an algorithm";
            case human {
                leaf human {
                    type empty;
                    description
                        "This option is used if a human provided the label";

                }
            }
            case algorithm {
                leaf algorithm {
                    type empty;
                    description
                        "This option is used if a software provided the label";
                }
            }
        }
    }

    grouping anomaly-grouping {
        description "List of anomalies that are part of the relevant state";
        list anomalies {
            key "id version";
            description "List of Anomaly instances";
            leaf id {
                type yang:uuid;
                description
                    "Unique ID of the anomaly";
            }
            leaf uri {
                type inet:uri;
                description
                    "URI to viusalize the analytical metrics of the anomaly.";
            }
            leaf version {
                type yang:counter32;
                description
                        "Version of the anomaly metadata object.
                        It allows multiple versions of the metadata to be
                        generated in order to support the definition of
                        multiple problem objects from the same source to
                        facilitate improvements overtime";
            }
            leaf state {
                type identityref {
                    base network-anomaly-state;
                }
                mandatory true;
                description "State of the anomaly";
            }		   
            leaf description {
                type string;
                description
                    "Textual description of the anomaly";
            }
            leaf start-time {
                type yang:date-and-time;
                mandatory true;
                description
                    "Date and time indicating the beginning of the anomaly
                    A detection system will alwasys set a start time, 
                    as it represents the moment in time from which the 
                    behaviour of the monitored system is considered 
                    to be anomalous with respect its expected behaviour";
            }
            leaf end-time {
                type yang:date-and-time;
                description
                    "Date and time indicating the end of the anomaly.
                    This field is indicated as non mandatory, as it could 
                    be the case that the anomaly is still happening at the 
                    time of generation of the label";
            }
            leaf confidence-score {
                type score;
                mandatory true;
                description "Score indicating how confident was the detector
                while considering the given anomaly as part of the relevant
                event";
            }
            leaf pattern {
                type identityref {
                    base pattern;
                }
                description
                    "Pattern describes the type of pattern that was
                    detected by the annotator (e.g. spike, drop, mean-shift,
                    etc.)";
            }
            container annotator {
                presence "It specifies an annotator for the anomaly";
                description
                    "Annotator represents the entity that produced the
                    annotation";
                uses annotator-grouping;
            }
            container symptom {
                presence "It specifies the symptom for the anomaly";
                description
                    "An observable Characteristic, State, Event, or Condition
                    considered as an indication of a Problem or potential
                    Problem";
                leaf id {
                    type yang:uuid;
                    mandatory true;
                    description
                        "Unique ID of the symptom type";
                }
                leaf concern-score {
                    type score;
                    mandatory true;
                    description
                        "Score indicating the degree of concern in relation
                         to the specified symptom";

                }
            }
            container service {
                presence
                    "It specifies the service (or the monitored entity)
                    affected by the anomaly";
                description
                    "Service represents the entity that is monitored, which
                    for instance can be a connectivity servise, such as an
                    L3VPN";

                leaf id {
                    type yang:uuid;
                    mandatory true;
                    description
                        "Unique ID of the service (or monitored entity)
                        This is supposed to be augmented by other modules
                        that want to define the service affected by the 
                        anomaly";
                }
            }
        }
    }

    notification relevant-state-notification {
        description
            "Notification of a relevant state that can be sent by the
            anomaly detection system to the postmortem management system or to the
            incident management system";
        uses relevant-state-grouping;
        uses anomaly-grouping;
    }
    
    container relevant-state {
        description "A Relevant State is a state that have relevancy
            for network operators, as those are states that could lead
            to problems or might be clear indications of problem already
            happening";
        leaf id {
            type yang:uuid;
            config false;
            mandatory true;
            description
                "Unique ID of the relevant state
                It is unique in the scope of the Label Store";

        }
        uses relevant-state-grouping;
        uses anomaly-grouping;
    }
}
