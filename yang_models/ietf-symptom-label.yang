module ietf-symptom-label {
    yang-version 1.1;
    namespace "urn:ietf:params:xml:ns:yang:ietf-symptom-label";
    prefix symptom_labelling;

    import ietf-yang-types {
        prefix yang;
        reference
          "RFC 6991: Common YANG Data Types";
    }

    organization
        "TBD";
    contact
        "TBD";
    description
        "This module defines objects for the description of symptoms identified
         within observability data, produced by devices, such as network nodes.
         Symptoms represent behaviours that are unexpected or undesired with
         respect to the context in which they are identified.

         This can be intended to be measured by mean of counters and gauges
         collected from the network nodes, as well as logs, and other forms of
         real time data that is collected and exported, with the scope to be
         further analysed.

         The module proposed in this document aims at adding meaningful metadata
          to the incident data itself.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).";

    revision 2023-10-30 {
        description
          "Initial version";
        reference
          "IETF Draft: Network Symptom Detection Labels";
    }

    grouping symptoms {
        container symptoms {
            list symptom {
                key "id";
                leaf id {
                    type string;
                    mandatory "true";
                    description
                      "Unique ID of the symptom";
                }
                leaf description {
                    type string;
                    mandatory "true";
                    description
                      "Textual description of the symptom";
                }
                list metrics {
                    key "metric";
                    leaf metric {
                        type string;
                        mandatory "true";
                        description
                          "Name of the metric affected by the symptom";
                    }
                }
                leaf start-time {
                    type yang:date-and-time;
                    mandatory "true";
                    description
                      "Date and time indicating the beginning of the symptom";
                }
                leaf end-time {
                    type yang:date-and-time;
                    mandatory "true";
                    description
                      "Date and time indicating the end of the symptom";
                }
                leaf concern {
                    type uint8;
                    mandatory "false";
                    description
                        "Degree of concern related to the symptom";
                }
                container source {
                    choice source-type {
                        mandatory "true";
                        case human {
                            leaf human {
                                mandatory "true";
                                type empty;
                            }
                        }
                        case algorithm {
                            leaf algorithm {
                                mandatory "true";
                                type empty;
                            }
                        }
                    }
                    leaf name {
                        mandatory "false";
                        type string;
                    }
                }
                choice plane {
                    mandatory "false";
                    description
                        "Network Plane affected by the symptom";
                    case forwarding-plane {
                        leaf forwarding-plane {
                            mandatory "true";
                            type empty;
                        }
                    }
                    case control-plane {
                        leaf control-plane {
                            mandatory "true";
                            type empty;
                        }
                    }
                    case management-plane {
                        leaf management-plane {
                            mandatory "true";
                            type empty;
                        }
                    }
                }
                choice outlier-type {
                    mandatory "false";
                    description
                        "Type of symptom / anomaly";
                    case global {
                        leaf global {
                            mandatory "true";
                            type empty;
                        }
                    }
                    case contextual {
                        leaf contextual {
                            mandatory "true";
                            type empty;
                        }
                    }
                    case collective {
                        leaf collective {
                            mandatory "true";
                            type empty;
                        }
                    }
                    case other {
                        leaf other {
                            mandatory "true";
                            type empty;
                        }
                    }
                }
                leaf action {
                    mandatory "false";
                    type string;
                }
                leaf reason {
                    mandatory "false";
                    type string;
                }
                leaf relation {
                    mandatory "false";
                    type string;
                }
            }
        }
    }
    uses symptoms;
}
