module ietf-symptom-semantic-metadata {
    yang-version 1.1;
    namespace "urn:ietf:params:xml:ns:yang:ietf-symptom-label";
    prefix symptom_labelling;

    import ietf-yang-types {
        prefix yang;
        reference
          "RFC 6991: Common YANG Data Types";
    }

    organization
        "TBD";
    contact
        "TBD";
    description
        "This module defines objects for the description of symptoms identified
         within observability data, produced by devices, such as network nodes.
         Symptoms represent behaviours that are unexpected or undesired with
         respect to the context in which they are identified.

         This can be intended to be measured by mean of counters and gauges
         collected from the network nodes, as well as logs, and other forms of
         real time data that is collected and exported, with the scope to be
         further analysed.

         The module proposed in this document aims at adding meaningful metadata
          to the incident data itself.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).";

    revision 2024-04-14 {
        description
          "Initial version";
        reference
          "IETF Draft: Network Symptom Detection Labels";
    }

    grouping symptom-group {
        container symptom {
            leaf id {
                type yang:uuid;
                mandatory "true";
                description
                    "Unique ID of the symptom type";
            }
            leaf event-id {
                type yang:uuid;
                mandatory "true";
                description "Reference to the network event this symptom is part of";
            }
            leaf description {
                type string;
                mandatory "true";
                description
                    "Textual description of the symptom";
            }
            leaf start-time {
                type yang:date-and-time;
                mandatory "true";
                description
                    "Date and time indicating the beginning of the incident";
            }
            leaf end-time {
                type yang:date-and-time;
                mandatory "true";
                description
                    "Date and time indicating the end of the incident";
            }
            leaf confidence-score {
                mandatory "true";
                type float {
                    range "0 .. 1";
                }
            }
            leaf concern-score {
                type float {
                    range "0 .. 1";
                }
            }
            list tags {
                key "key";
                leaf key {
                    type "string";
                    mandatory "true";
                }
                leaf value {
                    type "string";
                    mandatory "true";
                }
            }
            choice pattern {
                mandatory "false";
                description
                    "Network Plane affected by the symptom";
                case drop {
                    leaf drop {
                        mandatory "true";
                        type empty;
                    }
                }
                case spike {
                    leaf spike {
                        mandatory "true";
                        type empty;
                    }
                }
                case mean-shift {
                    leaf mean-shift {
                        mandatory "true";
                        type empty;
                    }
                }
                case seasonality-shift {
                    leaf seasonality-shift {
                        mandatory "true";
                        type empty;
                    }
                }
                case trend {
                    leaf trend {
                        mandatory "true";
                        type empty;
                    }
                }
                case other {
                    leaf other {
                        type string;
                        mandatory "true";
                        description "specify the type";
                    }
                }
            }
            container annotator {
                choice annotator-type {
                    mandatory "true";
                    case human {
                        leaf human {
                            mandatory "true";
                            type empty;
                        }
                    }
                    case algorithm {
                        leaf algorithm {
                            mandatory "true";
                            type empty;
                        }
                    }
                }
                leaf name {
                    mandatory "false";
                    type string;
                }   
            }
        }
    }
    uses symptom-group;
}
