module ietf-incident-semantic-metadata {
    yang-version 1.1;
    namespace "urn:ietf:params:xml:ns:yang:ietf-incident-label";
    prefix incident_labelling;

    import ietf-yang-types {
        prefix yang;
        reference
          "RFC 6991: Common YANG Data Types";
    }

    import ietf-symptom-semantic-metadata {
        prefix symptom-metadata;
    }

    organization
        "TBD";
    contact
        "TBD";
    description
        "This module defines objects for the description of network incidents.
         Incidents are a collection of observability data produced by devices,
         such as network nodes, that represent the behaviour of the system over
         time.

         This can be intended to be measured by mean of counters and gauges
         collected from the network nodes, as well as logs, and other forms of
         real time data that is collected and exported, with the scope to be
         further analysed.

         The module proposed in this document aims at adding meaningful metadata
          to the incident data itself.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).";

    revision 2023-10-30 {
        description
          "Initial version";
        reference
          "IETF Draft: Network Incident Detection Labels";
    }

    container incident {
        leaf id {
            type yang:uuid;
            mandatory "true";
            description
                "Unique ID of the network incident";
        }
        leaf description {
            type string;
            mandatory "true";
            description
                "Textual description of the incident";
        }
        leaf start-time {
            type yang:date-and-time;
            mandatory "true";
            description
                "Date and time indicating the beginning of the incident";
        }
        leaf end-time {
            type yang:date-and-time;
            mandatory "true";
            description
                "Date and time indicating the end of the incident";
        }
        list symptoms {
            uses symptom-metadata:symptom-group;
        }
        container annotator {
                choice type {
                    mandatory "true";
                    case human {
                        leaf human {
                            mandatory "true";
                            type empty;
                        }
                    }
                    case algorithm {
                        leaf algorithm {
                            mandatory "true";
                            type empty;
                        }
                    }
                }
                leaf name {
                    mandatory "false";
                    type string;
                }   
            }
    }
}
