module ietf-symptom-semantic-metadata {
    yang-version 1.1;
    namespace "urn:ietf:params:xml:ns:yang:ietf-symptom-semantic-metadata";
    prefix sm;

    import ietf-yang-types {
        prefix yang;
        reference
          "RFC 6991: Common YANG Data Types";
    }

  organization "IETF NMOP (Network Management Operations) Working Group";
  contact
    "WG Web:   <http:/tools.ietf.org/wg/netconf/>
     WG List:  <mailto:nmop@ietf.org>

     Authors:  Thomas Graf
               <mailto:thomas.graf@swisscom.com>
               Wanting Du
               <mailto:wanting.du@swisscom.com>
               Alex Huang Feng
               <mailto:alex.huang-feng@insa-lyon.fr>
               Vincenzo Riccobene
               <mailto:vincenzo.riccobene@huawei-partners.com>
               Antonio Roberto
               <mailto:antonio.roberto@huawei.com>";
    description
        "This module defines symptom objects to be used by a network
         anomaly detection system. The defined objects can be used to
         augment operational network collected observability data and 
         analytical problem data equally. Describing the observed
         symptoms, confidence and concern scores and outlier patterns.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).

         This version of this YANG module is part of RFC XXXX; see the RFC
         itself for full legal notices.";

    revision 2024-06-29 {
        description
          "Initial version";
        reference
          "RFC XXX: Semantic Metadata Annotation for Network Anomaly Detection";
    }

    typedef score {
      type uint8 {
        range "0 .. 1";
      }
    }

    grouping symptom-group {
        container symptom {
            leaf id {
                type yang:uuid;
                description
                    "Unique ID of the symptom type";
            }
            leaf event-id {
                type yang:uuid;
                description "Reference to the network event this symptom is part of";
            }
            leaf description {
                type string;
                description
                    "Textual description of the symptom";
            }
            leaf start-time {
                type yang:date-and-time;
                description
                    "Date and time indicating the beginning of the symptom";
            }
            leaf end-time {
                type yang:date-and-time;
                description
                    "Date and time indicating the end of the symptom";
            }
            leaf confidence-score {
                type score;
            }
            leaf concern-score {
                type score;
            }
            list tags {
                key "key";
                leaf key {
                    type "string";
                    mandatory "true";
                }
                leaf value {
                    type "string";
                    mandatory "true";
                }
            }
            choice pattern {
                mandatory "false";
                description
                    "Network Plane affected by the symptom";
                case drop {
                    leaf drop {
                        mandatory "true";
                        type empty;
                    }
                }
                case spike {
                    leaf spike {
                        mandatory "true";
                        type empty;
                    }
                }
                case mean-shift {
                    leaf mean-shift {
                        mandatory "true";
                        type empty;
                    }
                }
                case seasonality-shift {
                    leaf seasonality-shift {
                        mandatory "true";
                        type empty;
                    }
                }
                case trend {
                    leaf trend {
                        mandatory "true";
                        type empty;
                    }
                }
                case other {
                    leaf other {
                        type string;
                        mandatory "true";
                        description "specify the type";
                    }
                }
            }
            container annotator {
                choice annotator-type {
                    mandatory "true";
                    case human {
                        leaf human {
                            mandatory "true";
                            type empty;
                        }
                    }
                    case algorithm {
                        leaf algorithm {
                            mandatory "true";
                            type empty;
                        }
                    }
                }
                leaf name {
                    mandatory "false";
                    type string;
                }   
            }
        }
    }
}
