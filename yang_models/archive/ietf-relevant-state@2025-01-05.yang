module ietf-relevant-state {
    yang-version 1.1;
    namespace "urn:ietf:params:xml:ns:yang:ietf-relevant-state";
    prefix rsn;

    import ietf-yang-types {
        prefix yang;
        reference
          "RFC 6991: Common YANG Data Types";
    }

  organization "IETF NMOP (Network Management Operations) Working Group";
  contact
    "WG Web:   <http:/tools.ietf.org/wg/netconf/>
     WG List:  <mailto:nmop@ietf.org>

     Authors:  Thomas Graf
               <mailto:thomas.graf@swisscom.com>
               Wanting Du
               <mailto:wanting.du@swisscom.com>
               Alex Huang Feng
               <mailto:alex.huang-feng@insa-lyon.fr>
               Vincenzo Riccobene
               <mailto:vincenzo.riccobene@huawei-partners.com>
               Antonio Roberto
               <mailto:antonio.roberto@huawei.com>";
    description
        "This module defines the symptom conatiner to be used by a network
         anomaly detection system. The defined objects can be used to
         augment operational network collected observability data and 
         analytical problem data equally. Describing the relevant-state
		 of observed symptoms.

         Copyright (c) 2023 IETF Trust and the persons identified as
         authors of the code.  All rights reserved.

         Redistribution and use in source and binary forms, with or
         without modification, is permitted pursuant to, and subject
         to the license terms contained in, the Revised BSD License
         set forth in Section 4.c of the IETF Trust's Legal Provisions
         Relating to IETF Documents
         (https://trustee.ietf.org/license-info).

         This version of this YANG module is part of RFC XXXX; see the RFC
         itself for full legal notices.";

    revision 2025-01-05 {
        description
          "Initial version";
        reference
          "RFC XXX: Semantic Metadata Annotation for Network Anomaly Detection";
    }

    typedef score {
		description
		"Score typedef.";
        type uint8 {
            range "0 .. 100";
        }
    }
    identity network-anomaly-state {
		description
		"Base identity for representing the state of the network anomaly.";
    }
	identity network-anomaly-detection {
		base network-anomaly-state;
		description
		"A problem reached detection state.";
	}
	identity network-anomaly-validation {
		base network-anomaly-state;
		description
		"A problem reached validation state.";
	}
	identity network-anomaly-refinement {
		base network-anomaly-state;
		description
		"A problem reached refinement state.";
	}
    identity problem-forecasted {
		base network-anomaly-detection;
		description
		"A problem has been forecasted, as it is expected that
		the indicated list of symptoms will impact a service
		in the near future.";
	}
	identity problem-potential {
		base network-anomaly-detection;
		description
		"A problem has been detected with a confidence
		lower than 100%. In order to confirm that this set of
		symptoms are generating service impact, it requires further
		validation.";
	}
	identity problem-confirmed {
		base network-anomaly-validation;
		description
		"After validation, the problem has been confirmed.";
	}
	identity discarded {
		base network-anomaly-validation;
		description
		"After validation, the network anomaly has been
		discarded, as there is no evindence that it is causing an
		problem.";
	}
	identity analyzed {
		base network-anomaly-refinement;
		description
		"The anomaly detection went through analysis to identify
		potential ways to further improve the detection process in
		for future anomalies.";
	}
	identity adjusted {
		base network-anomaly-refinement;
		description
		"The network anomaly has been solved and analysed.
		No further action is required.";
	}

    grouping relevant-state-grouping {
		description
		"Relevant State Grouping.";
        leaf id {
            mandatory true;
            type yang:uuid;
            description
                "Unique ID of the fault.";
        }
        leaf uri {
            type yang:uri;
            description
                "URI to visualize the analytical metrics of the fault.";
        }
        leaf description {
            type string;
            description
                "Textual description of the fault.";
        }
        leaf start-time {
            mandatory true;
            type yang:date-and-time;
            description
                "Date and time indicating the beginning of the fault.";
        }
        leaf end-time {
            type yang:date-and-time;
            description
                "Date and time indicating the end of the fault.";
        }
    }

    grouping annotator-grouping {
		"Annotator Grouping.";
        leaf name {
            mandatory true;
            type string;
        }
        choice annotator-type {
            case human {
                leaf human {
                    type empty;
                }
            }
            case algorithm {
                leaf algorithm {
                    type empty;
                }
            }
        }
    }

    grouping symptom-grouping {
		"Symptom Grouping.";
        leaf id {
            mandatory true;
            type yang:uuid;
            description
                "Unique ID of the symptom type";
        }
        leaf uri {
            type yang:uri;
            description
                "URI to describe additional context to the symptom.";
        }
        leaf concern-score {
            mandatory true;
            type score;
        }
    }

    grouping service-grouping {
		"Service Grouping.";
        leaf id {
            mandatory true;
            type yang:uuid;
            description
                "Unique ID of the service (or monitored entity)";
        }
        leaf uri {
            type yang:uri;
            description
                "URI to describe additional context to the service.";
        }
    }

    grouping anomaly-grouping {
		"Anomaly Grouping.";
        list anomalies {
		    description "Anomaly leafs.";
            key "id version";
            leaf id {
                type yang:uuid;
                description
                    "Unique ID of the anomaly";
            }
			leaf uri {
				type yang:uri;
				description
					"URI to viusalize the analytical metrics of the anomaly.";
			}
            leaf version {
                type yang:counter32;
                description
                        "Version of the problem metadata object.
                        It allows multiple versions of the metadata to be
                        generated in order to support the definition of
                        multiple problem objects from the same source to
                        facilitate improvements overtime";
            }
            leaf state {
                mandatory true;
                type identityref {
                    base network-anomaly-state;
                }
                description "State of the anomaly.";
            }		   
            leaf description {
                type string;
                description
                    "Textual description of the anomaly";
            }
            leaf start-time {
                mandatory true;
                type yang:date-and-time;
                description
                    "Date and time indicating the beginning of the anomaly";
            }
            leaf end-time {
                type yang:date-and-time;
                description
                    "Date and time indicating the end of the anomaly";
            }
            leaf confidence-score {
                mandatory true;
                type score;
            }
            choice pattern {
                description
                    "Network Plane affected by the symptom";
                case drop {
                    leaf drop {
                        type empty;
                    }
                }
                case spike {
                    leaf spike {
                        type empty;
                    }
                }
                case mean-shift {
                    leaf mean-shift {
                        type empty;
                    }
                }
                case seasonality-shift {
                    leaf seasonality-shift {
                        type empty;
                    }
                }
                case trend {
                    leaf trend {
                        type empty;
                    }
                }
                case other {
                    leaf other {
                        type string;
                        description "specify the type";
                    }
                }
            }
            container annotator {
				description "Annotator container.";
                presence "It specifies an annotator for the anomaly";
                uses annotator-grouping;
            }
            container symptom {
				description "Symptom container.";
                presence "It specifies the symptom for the anomaly";
                uses symptom-grouping;
            }
            container service {
				description "Service container.";
                presence "It specifies the service (or the monitored entity) affected by the anomaly";
                uses service-grouping;
            }
        }
    }

    notification relevant-state-notification {
        uses relevant-state-grouping;
        uses anomaly-grouping;
    }
    
    container relevant-state {
        uses relevant-state-grouping;
        uses anomaly-grouping;
    }

}
