module ietf-relevant-state {
  yang-version 1.1;
  namespace "urn:ietf:params:xml:ns:yang:ietf-relevant-state";
  prefix rsn;

  import ietf-yang-types {
    prefix yang;
    reference
      "draft-ietf-netmod-rfc6991-bis-18: Common YANG Data Types";
  }
  import ietf-inet-types {
    prefix inet;
    reference
      "draft-ietf-netmod-rfc6991-bis-18: Common YANG Data Types";
  }

  organization
    "IETF NMOP Working Group";
  contact
    "WG Web:   <https://datatracker.ietf.org/wg/nmop/>
     WG List:  <mailto:nmop@ietf.org>

     Editor:   Vincenzo Riccobene
              <mailto:vincenzo.riccobene@huawei-partners.com>
              Thomas Graf
              <mailto:thomas.graf@swisscom.com>
              Wanting Du
              <mailto:wanting.du@swisscom.com>
              Alex Huang Feng
              <mailto:alex.huang-feng@insa-lyon.fr>";
  description
    "This module defines the relevant-state container and
     notifications to be used by a network anomaly detection
     system. The defined objects can be used to augment
     operational network collected observability data and
     analytical problem data equally. Describing the relevant-state
     of observed symptoms.

     Copyright (c) 2025 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry
     (https://www.iana.org/assignments/yang-parameters).

     This version of this YANG module is part of RFC XXXX; see
     the RFC itself for full legal notices.";

  revision 2025-11-15 {
    description
      "Initial version";
    reference
      "RFC XXX: Semantic Metadata Annotation for Network Anomaly
       Detection";
  }

  typedef score {
    type uint8 {
      range "0..100";
    }
    description
      "Number that indicates a score between 0 and 100.";
  }

  identity network-anomaly-stage {
    description
      "Base identity for representing the of the network anomaly
       stage.";
    reference
      "Section 6 in draft-ietf-nmop-network-anomaly-lifecycle.";
  }

  identity detection {
    base network-anomaly-stage;
    description
      "A problem is int the detection stage.";
    reference
      "Section 6.1 in draft-ietf-nmop-network-anomaly-lifecycle.";
  }

  identity validation {
    base network-anomaly-stage;
    description
      "A problem is int the validation stage.";
    reference
      "Section 6.2 in draft-ietf-nmop-network-anomaly-lifecycle.";
  }

  identity refinement {
    base network-anomaly-stage;
    description
      "A problem is int the refinement stage.";
    reference
      "Section 6.3 in draft-ietf-nmop-network-anomaly-lifecycle.";
  }

  identity problem-forecasted {
    base detection;
    description
      "A problem has been forecasted, as it is expected that
       the indicated list of symptoms will impact a service
       in the near future.";
  }

  identity problem-potential {
    base detection;
    description
      "A problem has been detected with a confidence
       lower than 100%. In order to confirm that this set of
       symptoms are generating service impact, it requires further
       validation.";
  }

  identity problem-confirmed {
    base validation;
    description
      "After validation, the problem has been confirmed.";
  }

  identity discarded {
    base validation;
    description
      "After validation, the network anomaly has been
       discarded, as there is no evindence that it is causing a
       problem.";
  }

  identity analyzed {
    base refinement;
    description
      "The anomaly detection went through analysis to identify
       potential ways to further improve the detection process in
       for future anomalies.";
  }

  identity adjusted {
    base refinement;
    description
      "The network anomaly has been solved and analysed.
       No further action is required.";
  }

  identity pattern {
    description
      "Pattern identified by the Detector.";
  }

  identity drop {
    base pattern;
    description
      "Drop of the value.";
  }

  identity spike {
    base pattern;
    description
      "Spike of the value.";
  }

  identity mean-shift {
    base pattern;
    description
      "Shift of the mean of the value.";
  }

  identity seasonality-shift {
    base pattern;
    description
      "Shift of the seasonality of the value.";
  }

  identity trend {
    base pattern;
    description
      "Trend exhibited by the value.";
  }

  identity other {
    base pattern;
    description
      "Any other type of pattern.";
  }

  grouping relevant-state-grouping {
    description
      "Relevant State is a state that could lead to
       problems or might be clear indications of problem
       already happening.";
    reference
      "Figure 4 in draft-ietf-nmop-terminology.";
    leaf id {
      type yang:uuid;
      mandatory true;
      description
        "Unique ID of the relevant state. It is unique
         in the scope of the Label Store.";
    }
    leaf uri {
      type inet:uri;
      description
        "URI to viusalize the analytical metrics of the
         relevant-state.";
    }
    leaf description {
      type string;
      description
        "Textual description of the fault.";
    }
    leaf start-time {
      type yang:date-and-time;
      mandatory true;
      description
        "Date and time indicating the beginning of the problem.";
    }
    leaf end-time {
      type yang:date-and-time;
      description
        "Date and time indicating the end of the problem.";
    }
    leaf strategy {
      type string;
      mandatory false;
      description
        "Captures one approach to look at the data (as a human operator
         does) to observe if an abnormal situation is arising.";
      reference
        "Section 3.5.3 in
         draft-ietf-nmop-network-anomaly-architecture.";
    }
    leaf confidence-score {
      type score;
      description
        "Indicates how confident the detector detected an outlier. The
         higher the value the higher the confidence in relation to the
         overall relevant state.";
    }
    leaf concern-score {
      type score;
      mandatory true;
      description
        "Indicates how concerned network operation on connectivity
         service degradation should be. The higher the value the higher
         the concern in relation to the overall relevant state.";
    }
    leaf stage {
      type identityref {
        base network-anomaly-stage;
      }
      mandatory true;
      description
        "Stage of the relevant state.";
    }
    choice service {
      description
        "Indication of the service that is affected
         (or potentially affected) by the relevant state";
    }
  }

  grouping annotator-grouping {
    description
      "Annotator represents the entity that produced the
       annotation (it is either a human or an algorithm).";
    leaf id {
      type yang:uuid;
      description
        "Unique ID of the annotator (either user or algorithm).";
    }
    leaf name {
      type string;
      mandatory true;
      description
        "Name of the annotator (either user or algorithm).";
    }
    leaf version {
      type string;
      mandatory false;
      description
        "Version of the annotator.";
    }
    leaf annotator-type {
      type enumeration {
        enum human {
          description
            "This option is used if a human provided the label.";
        }
        enum algorithm {
          description
            "This option is used if a algorithm or software
             provided the label.";
        }
      }
      description
        "An annotator can be either a human user or a
         programmatic entity, such as an algorithm.";
    }
  }

  grouping message-broker-grouping {
    description
      "References message broker draft-ietf-nmop-yang-message-broker-integration entities.";
    leaf topic-name {
      type inet:host-name;
      description
        "From which message broker topic the operational data was consumed from.";
    }
    leaf subject-name {
      type inet:host-name;
      description
        "To which message broker subject the operational data references to.";
    }
  }

  grouping anomaly-grouping {
    description
      "List of anomalies that are part of the relevant state";
    list anomaly {
      key "id revision";
      description
        "List of Anomaly instances.";
      leaf id {
        type yang:uuid;
        description
          "Unique identifier of the anomaly.";
      }
      leaf revision {
        type yang:counter32;
        description
          "Revision of the anomaly metadata object.
            It allows multiple revisions of the metadata to be
            generated in order to support the definition of
            multiple problem objects from the same source to
            facilitate improvements overtime.";
      }
      leaf uri {
        type inet:uri;
        description
          "URI to viusalize the analytical metrics of the
           anomaly.";
      }
      leaf stage {
        type identityref {
          base network-anomaly-stage;
        }
        mandatory true;
        description
          "Stage of the anomaly.";
      }
      leaf description {
        type string;
        description
          "Textual description of the anomaly.";
      }
      leaf start-time {
        type yang:date-and-time;
        mandatory true;
        description
          "Date and time indicating the beginning of the anomaly.
            A detection system will alwasys set a start time,
            as it represents the moment in time from which the
            behaviour of the monitored system is considered
            to be anomalous with respect its expected behaviour.";
      }
      leaf end-time {
        type yang:date-and-time;
        description
          "Date and time indicating the end of the anomaly.
            This field is indicated as non mandatory, as it could
            be the case that the anomaly is still happening at the
            time of generation of the label.";
      }
      leaf confidence-score {
        type score;
        description
          "Indicates how confident the detector detected an outlier. The
           higher the value the higher the confidence in relation to the
           anomaly.";
      }
      leaf pattern {
        type identityref {
          base pattern;
        }
        description
          "Pattern describes the type of pattern that was
            detected by the annotator (e.g. spike, drop,
            mean-shift, etc.).";
      }
      container annotator {
        description
          "Annotator represents the entity that produced the
            annotation.";
        uses annotator-grouping;
      }
      container operational-data {
        description
          "References the operational data from where the anomaly was observed.";
        uses message-broker-grouping;
      }
      container symptom {
        presence "It specifies the symptom for the anomaly";
        description
          "An observable Characteristic, State, Event, or
           Condition considered as an indication of a Problem
           or potential Problem.";
        leaf id {
          type yang:uuid;
          mandatory true;
          description
            "Unique identifier of the symptom type.";
        }
        leaf concern-score {
          type score;
          mandatory true;
          description
            "Score indicating the degree of concern in
              relation to the specific symptom. Each
              symptom will carry a certain degree of
              concern that is specific to the symptom.";
        }
      }
    }
  }

  notification relevant-state-notification {
    description
      "Notification of a relevant state that can be sent by the
       anomaly detection system to the postmortem management
       system or to the incident management system.";
    container publisher {
      description
        "Publisher represents the entity that produced the
          relevant-state.";
      leaf id {
        type yang:uuid;
        description
          "Unique ID of the publisher.";
      }
      leaf name {
        type string;
        mandatory true;
        description
          "Name of the publisher.";
      }
      leaf version {
        type string;
        mandatory false;
        description
          "Version of the publisher.";
      }
    }
    uses relevant-state-grouping;
    uses anomaly-grouping;
  }

  container relevant-state {
    description
      "A Relevant State is a state that have relevancy
       for network operators, as those are states that could lead
       to problems or might be clear indications of problem already
       happening.";
    uses relevant-state-grouping;
    uses anomaly-grouping;
  }
}
